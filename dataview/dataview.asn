CFDP-PROTOCOL DEFINITIONS ::=
BEGIN

maxFileNameSizeLength INTEGER ::= 128

maxListingFileNameSizeLength INTEGER ::= 120

DirectiveCode ::= INTEGER (0..255)

DirectiveSubtypeCode ::= ENUMERATED {
   ack-others (0),
   ack-finished (1)
}

ConditionCode ::= ENUMERATED {
   no-error (0),
   positive-ack-limit-reached (1),
   keep-alive-limit-reached (2),
   invalid-transmission-mode (3),
   filestore-rejection (4),
   file-checksum-failure (5),
   file-size-error (6),
   nak-limit-reached (7),
   inactivity-detected (8),
   invalid-file-structure (9),
   check-limit-reached (10),
   unsupported-checksum-type (11),
   suspend-request-received (14),
   cancel-request-received (15)
}

FileChecksum ::= INTEGER (0..4294967295)

FileSize ::= INTEGER (0..4294967295)

AckTransactionStatus ::= ENUMERATED {
   undefined (0),
   active (1),
   terminated (2),
   unrecognized (3)
}

DeliveryCode ::= ENUMERATED {data-complete (0), data-incomplete (1)}

ClosureRequested ::= ENUMERATED {requested (0), not-requested (1)}

ChecksumType ::= ENUMERATED {
   modular (0),
   none (15)
}

FileNameSize ::= INTEGER (0..maxFileNameSizeLength)

FileName ::= OCTET STRING (SIZE(0..maxFileNameSizeLength))

FileStatus ::= ENUMERATED {
   discarted-deliberately (0),
   discarted-file-rejection (1),
   retained-successfully (2),
   unreported (3)
}

SegmentOffset ::= INTEGER (0..4294967295)

-- FileData size indicates maximum size of file data segment sent in File data PDUDataFieldLength
-- It can be changed to configure maximum file segment size
FileData ::= OCTET STRING (SIZE(0..4096))

ResponseRequired ::= ENUMERATED {nak (0), keep-alive (1)}

Progress ::= INTEGER (0..4294967295)

TransactionStatus ::= ENUMERATED {
   discarted-deliberately (0),
   discarted-file-rejection (1),
   retained-successfully (2),
   unreported (3)
}

TypeFieldCode ::= ENUMERATED {
   filestore-request (0),
   filestore-response (1),
   message-to-user (2),
   fault-handler-overrides (4),
   flow-label (5),
   entity-id (6)
}

MessageType ::= ENUMERATED {
   originating-transaction-id (10),
   directory-listing-request (16),
   directory-listing-response (17)
}

PDUType ::= INTEGER (0 .. 1)

Version ::= INTEGER (0 .. 7)

Direction ::= ENUMERATED {toward-receiver (0), toward-sender (1)}

TransmissionMode ::= ENUMERATED {acknowledged (0), unacknowledged (1)}

CRCFlag ::= ENUMERATED {crc-not-present (0), crc-present (1)}

LargeFileFlag ::= INTEGER (0..1)

PDUDataFieldLength ::= INTEGER (0 .. 65535)

SegmentationControl ::= ENUMERATED {record-boundries-not-preserved (0), record-boundries-preserved (1)}

LengthOfEntityIds ::= INTEGER (0 .. 7)

SegmentMetadataFlag ::= ENUMERATED {flag-present (0), flag-not-present (1)}

LengthOfTransactionSequenceNumber ::= INTEGER (0 .. 7)

EntityId ::= OCTET STRING (SIZE(1..7))

TransactionSequenceNumber ::= OCTET STRING (SIZE(1..7))

ListingResponseCode ::= ENUMERATED {successful (0), unsuccessful (1)}

ListingFileNameSize ::= INTEGER (0..maxListingFileNameSizeLength)

ListingFileName ::= OCTET STRING (SIZE(0..maxListingFileNameSizeLength))

DirectoryListingRequest ::= SEQUENCE {
   directory-name ListingFileName,
   directory-file-name ListingFileName
}

DirectoryListingResponse ::= SEQUENCE {
   listing-response-code ListingResponseCode,
   directory-name ListingFileName,
   directory-file-name ListingFileName
}

OriginatingTransactionId ::= SEQUENCE {
   source-entity-id EntityId,
   transaction-sequence-number TransactionSequenceNumber
}

MessageToUser ::= CHOICE {
   originating-transaction-id OriginatingTransactionId,
   directory-listing-request DirectoryListingRequest,
   directory-listing-response DirectoryListingResponse
}

MessageToUserWithHeader ::= SEQUENCE {
   message-to-user MessageToUser
}

TLV ::= SEQUENCE {
   length-value CHOICE {
      message-to-user SEQUENCE {
         value OCTET STRING (CONTAINING MessageToUserWithHeader)
      }
   }
}

PDUHeader ::= SEQUENCE {
   version Version,
   direction Direction,
   transmission-mode TransmissionMode,
   crc-flag CRCFlag,
   source-entity-id EntityId,
   transaction-sequence-number TransactionSequenceNumber,
   destination-entity-id EntityId
}

EofPDU ::= SEQUENCE {
   condition-code ConditionCode,
   file-checksum FileChecksum,
   file-size FileSize
}

FinishedPDU ::= SEQUENCE {
   condition-code ConditionCode,
   delivery-code DeliveryCode,
   file-status FileStatus
}

AckPDU ::= SEQUENCE {
   directive-code-of-ack-pdu DirectiveCode,
   directive-subtype-code DirectiveSubtypeCode,
   condition-code ConditionCode,
   transaction-status AckTransactionStatus
}

MetadataPDU ::= SEQUENCE {
   closure-requested ClosureRequested,
   checksum-type ChecksumType,
   file-size FileSize,
   source-file-name FileName,
   destination-file-name FileName
}

FileDataPDU ::= SEQUENCE {
   segment-offset SegmentOffset,
   file-data FileData
}

FileDirectivePDU ::= CHOICE {
   eof-pdu EofPDU,
   finished-pdu FinishedPDU,
   ack-pdu AckPDU,
   metadata-pdu MetadataPDU
}

FileDataType ::= SEQUENCE {
   file-data-pdu FileDataPDU
}

FileDirectiveType ::= SEQUENCE {
   file-directive-pdu FileDirectivePDU
}

PayloadData ::= CHOICE {
   file-directive FileDirectiveType,
   file-data FileDataType
}

CfdpPDU ::= SEQUENCE {
   pdu-header PDUHeader,
   payload OCTET STRING (CONTAINING PayloadData)
}



END
